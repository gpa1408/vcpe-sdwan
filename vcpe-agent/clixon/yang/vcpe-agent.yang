module vcpe-agent {
  yang-version 1.1;
  namespace "urn:vcpe:agent";
  prefix va;

  revision 2026-04-18 {
    description "Minimal vcpe agent model";
  }

  container agent {
    leaf enabled {
      type boolean;
      default true;
    }

    leaf controller-url {
      type string;
    }

    leaf last-status {
      config false;
      type string;
    }
  }
}
