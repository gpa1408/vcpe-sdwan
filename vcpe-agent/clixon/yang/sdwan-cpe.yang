module sdwan-cpe {
  yang-version 1.1;
  namespace "urn:sdwan:cpe";
  prefix scpe;

  import ietf-inet-types {
    prefix inet;
  }

  organization
    "Thesis SD-WAN CPE model";
  contact
    "Author: Pamodi";
  description
    "YANG model for an SD-WAN CPE supporting underlay WAN links,
     LAN services, WireGuard-based overlays, traffic classification,
     policy-based steering, and operational state reporting";

  revision 2026-03-13 {
    description
      "revision3";
  }

  /*
   * ======================================================================================================
   * Typedefs
   * ======================================================================================================
   */
  typedef if-name {
    type string {
      length "1..64";
    }
    description
      "Interface name on the CPE, for example eth0, eth1";
  }

  typedef TL-id {
    type enumeration {
      enum UPL1;
      enum UPL2;
      enum UPL3;
      enum UPL4;
    }
    description
      "Transport link identifier";
  }

  typedef tunnel-name {
    type string {
      length "1..64";
    }
    description
      "Overlay tunnel identifier, for example wg0 or wg1";
  }

  typedef class-name {
    type string {
      length "1..64";
    }
    description
      "Traffic class name, for example voice, video, best-effort";
  }

  typedef wireguard-key {
    type string {
      pattern '[a-zA-Z0-9+/]{43}=';
      length "44";
    }
    description "A WireGuard public or private key (Base64 encoded, 44 chars).";
  }

  typedef percentage {
    type decimal64 {
      fraction-digits 2;
      range "0 .. 100";
    }
    units "%";
    description
      "Percentage value from 0 to 100";
  }

  typedef port-number-or-any {
    type union {
      type uint16;
      type enumeration {
        enum any;
      }
    }
    description
      "A single L4 port or the special value any";
  }

  /*
   * ===========================================================================================================
   * Root
   * ===========================================================================================================
   */
  container sdwan {
    description
      "Root container for SD-WAN CPE configuration and operational state";

    /*
     * ==================================================================================
     * Interface roles
     * ==================================================================================
     */
    container interfaces {
      description
        "Logical grouping of WAN and LAN interfaces";

      /*
       * ===================================================================================
       * 1. Underlay (WAN Links)
       * ===================================================================================
       */
      container underlay {
        description
          "Physical or logical WAN links used to reach the transport network";

        list wan-link {
          key "name";
          description
            "A WAN uplink such as fiber, broadband, or LTE";

          leaf name {
            type TL-id;
            description
              "Transport link identifier of the WAN interface";
          }

          leaf interface-name {
            type if-name;
            description
              "Interface name of the Transport link identifier";
          }

          leaf role {
            type enumeration {
              enum broadband;
              enum fiber;
              enum lte;
              enum ipvpn;
            }
            description
              "Administrative role or access type of this WAN link";
          }

          leaf admin-enabled {
            type boolean;
            default "true";
            description
              "Administrative enable or disable";
          }

          leaf address-mode {
            type enumeration {
              enum dhcp;
              enum static;
            }
            default "dhcp";
            description
              "IPv4 address assignment mode";
          }

          leaf static-address {
            when "../address-mode = 'static'";
            type inet:ipv4-prefix;
            description
              "Static IPv4 address with prefix length, for example 192.0.2.10/24";
          }

          leaf static-gateway {
            when "../address-mode = 'static'";
            type inet:ipv4-address;
            description
              "Default IPv4 gateway for static configuration";
          }

          leaf nat-type {
            type string;
            config false;
            description 
              "Detected NAT type of this WAN link.";
          }
        }
      }

      /*
       * =============================================================================
       * 2. LAN side
       * =============================================================================
       */
      container lan {
        description
          "LAN-facing interfaces and local subnet services";

        list lan-link {
          key "name";
          description
            "A LAN interface identifier";

          leaf name {
            type if-name;
            description
              "LAN interface name, for example eth0 or eth2";
          }

          leaf admin-enabled {
            type boolean;
            default "true";
            description
              "Administrative enable or disable";
          }

          leaf ipv4-prefix {
            type inet:ipv4-prefix;
            description
              "LAN IPv4 subnet, for example 10.10.0.1/24";
          }

          /*==========================LAN Services===========================*/
          container dhcp-server {
            description
              "Simple DHCP server settings for the LAN";

            leaf enabled {
              type boolean;
              default "false";
              description
                "DHCP server enable or disable";
            }

            leaf pool-start {
              when "../enabled = 'true'";
              type inet:ipv4-address;
              description
                "Start IPv4 address in the DHCP pool";
            }

            leaf pool-end {
              when "../enabled = 'true'";
              type inet:ipv4-address;
              description
                "Last IPv4 address in the DHCP pool";
            }

            leaf dns-server {
              when "../enabled = 'true'";
              type inet:ipv4-address;
              description
                "DNS server offered to clients";
            }

            leaf lease-time-seconds {
              when "../enabled = 'true'";
              type uint32;
              default "86400";
              description
                "DHCP lease time in seconds";
            }
          }
        }
      }
    }

    /*
     * ==============================================================================
     * 3. Overlay tunnels (WireGuard)
     * ==============================================================================
     */
    container overlay {
      description
        "WireGuard-based overlay tunnels used for SD-WAN connectivity";

      list tunnel {
        key "name";
        description
          "An overlay tunnel instance";

        leaf name {
          type tunnel-name;
          description
            "Tunnel name";
        }

        leaf bind-wan-link {
          type leafref {
            path "/scpe:sdwan/scpe:interfaces/scpe:underlay/scpe:wan-link/scpe:name";
          }
          mandatory true;
          description
            "WAN link (Transport link Identifier) used as the transport egress for this tunnel";
        }

        leaf admin-enabled {
          type boolean;
          default "true";
          description
            "Administrative enable or disable";
        }

        leaf local-address {
          type inet:ipv4-address;
          description
            "Local source IPv4 address used for the tunnel endpoint";
        }

        leaf local-port {
          type inet:port-number;
          default "51820";
          description
            "Local WireGuard UDP port";
        }

        leaf local-public-key {
          type string;
          config false;
          description
            "WireGuard public key generated by the CPE agent and exposed to the controller.";
        }

        leaf peer-address {
          type inet:ipv4-address;
          mandatory true;
          description
            "Remote WireGuard peer IPv4 address";
        }

        leaf peer-port {
          type inet:port-number;
          default "51820";
          description
            "Remote WireGuard peer UDP port";
        }

        leaf peer-public-key {
          type wireguard-key;
          mandatory true;
          description "Peer WireGuard Public Key";
        }

        leaf-list allowed-prefix {
          type inet:ip-prefix;
          min-elements 1;
          description
            "Allowed/routed prefixes at peer via this overlay tunnel";
        }

        leaf keepalive-seconds {
          type uint16;
          default "25";
          description
            "Persistent keepalive interval in seconds";
        }
      }
    }

    /*
     * =========================================================================================
     * Traffic classification
     * =========================================================================================
     */
    container traffic {
      description
        "Traffic class definitions and match criteria";

      list class {
        key "name";
        description
          "Named traffic class";

        leaf name {
          type class-name;
          description
            "Traffic class name";
        }

        leaf fwmark {
          config false;
          type uint32;
          description
            "Fwmark associated with this traffic class for Linux policy routing. Assigned by the CPE agent and used in steering policies";
        }

        container five-tuple {
          description
            "Five-tuple match criteria for packet classification";

          leaf src-prefix {
            type inet:ip-prefix;
            description
              "Source prefix to match";
          }

          leaf dst-prefix {
            type inet:ip-prefix;
            description
              "Destination prefix to match";
          }

          leaf l4-protocol {
            type enumeration {
              enum tcp;
              enum udp;
              enum icmp;
              enum any;
            }
            default "any";
            description
              "Layer 4 protocol to match";
          }

          leaf src-port {
            when "../l4-protocol = 'tcp' or ../l4-protocol = 'udp'";
            type port-number-or-any;
            default "any";
            description
              "Single source port match, or any";
          }

          leaf dst-port {
            when "../l4-protocol = 'tcp' or ../l4-protocol = 'udp'";
            type port-number-or-any;
            default "any";
            description
              "Single destination port match, or any";
          }
        }
      }
    }

    /*
     * ===================================================================================
     * Steering policy / Service Level Objective (SLO)
     * ===================================================================================
     */
    container policy {
      description
        "Maps traffic classes to steering behavior and SLO constraints";

      list steering {
        key "class";
        description
          "Steering rule for a traffic class";

        leaf class {
          type leafref {
            path "/scpe:sdwan/scpe:traffic/scpe:class/scpe:name";
          }
          description
            "Traffic class to which this policy applies";
        }

        leaf max-latency-ms {
          type uint32;
          units "ms";
          description
            "Maximum acceptable latency";
        }

        leaf max-jitter-ms {
          type uint32;
          units "ms";
          description
            "Maximum acceptable jitter";
        }

        leaf max-loss-percent {
          type percentage;
          description
            "Maximum acceptable packet loss percentage";
        }

        leaf min-bandwidth-kbps {
          type uint32;
          units "kbps";
          description
            "Minimum required bandwidth";
        }

        leaf steering-mode {
          type enumeration {
            enum load-balance;
            enum failover;
          }
          default "failover";
          description
            "Traffic steering method";
        }

        leaf load-balance-link-type {
          when "../steering-mode = 'load-balance'";
          type enumeration {
            enum tunnel;
            enum wan-link;
          }
          mandatory true;
          description
            "Traffic steering method";
        }

        leaf-list load-balance-tunnel {
          when "../steering-mode = 'load-balance' and ../load-balance-link-type = 'tunnel'";
          type leafref {
            path "/scpe:sdwan/scpe:overlay/scpe:tunnel/scpe:name";
          }
          description
            "Overlay tunnel names or underlay transport link IDs used for load balancing";
        }

        leaf-list load-balance-wan-link {
          when "../steering-mode = 'load-balance' and ../load-balance-link-type = 'wan-link'";
          type leafref {
            path "/scpe:sdwan/scpe:interfaces/scpe:underlay/scpe:wan-link/scpe:name";
          }
          description
            "Overlay tunnel names or underlay transport link IDs used for load balancing";
        }

        leaf failover-link-type {
          when "../steering-mode = 'failover'";
          type enumeration {
            enum tunnel;
            enum wan-link;
          }
          mandatory true;
          description
            "Traffic steering method";
        }

        leaf primary-tunnel {
          when "../steering-mode = 'failover' and ../failover-link-type = 'tunnel'";
          mandatory true;
          type leafref {
            path "/scpe:sdwan/scpe:overlay/scpe:tunnel/scpe:name";
          }
          description
            "Primary preferred overlay tunnel or underlay link";
        }

        leaf primary-wan-link {
          when "../steering-mode = 'failover' and ../failover-link-type = 'wan-link'";
          mandatory true;
          type leafref {
            path "/scpe:sdwan/scpe:interfaces/scpe:underlay/scpe:wan-link/scpe:name";
          }
          description
            "Primary preferred overlay tunnel or underlay link";
        }

        leaf-list secondary-tunnel {
          when "../steering-mode = 'failover' and ../failover-link-type = 'tunnel'";
          ordered-by user;
          type leafref {
            path "/scpe:sdwan/scpe:overlay/scpe:tunnel/scpe:name";
          }
          description
            "Secondary preferred overlay tunnel(s) or underlay link(s) used when the primary link is down";
        }

        leaf-list secondary-wan-link {
          when "../steering-mode = 'failover' and ../failover-link-type = 'wan-link'";
          ordered-by user;
          type leafref {
            path "/scpe:sdwan/scpe:interfaces/scpe:underlay/scpe:wan-link/scpe:name";
          }
          description
            "Secondary preferred overlay tunnel(s) or underlay link(s) used when the primary link is down";
        }
      }
    }

        /*
     * =====================================================================================================
     * Firewall
     * =====================================================================================================
     */
    container firewall {
      description
        "Firewall configuration";

      list rule {
        key "id";
        ordered-by user;
        description
          "Firewall rule";

        leaf id {
          type string {
            length "1..64";
          }
          description
            "Firewall rule identifier";
        }

        leaf action {
          type enumeration {
            enum allow;
            enum deny;
          }
          mandatory true;
          description
            "Firewall action";
        }

        leaf src-prefix {
          type inet:ip-prefix;
          description
            "Source prefix to match";
        }

        leaf dst-prefix {
          type inet:ip-prefix;
          description
            "Destination prefix to match";
        }

        leaf l4-protocol {
          type enumeration {
            enum tcp;
            enum udp;
            enum icmp;
            enum any;
          }
          default "any";
          description
            "Layer 4 protocol to match";
        }

        leaf src-port {
          when "../l4-protocol = 'tcp' or ../l4-protocol = 'udp'";
          type port-number-or-any;
          default "any";
          description
            "Single source port match, or any";
        }

        leaf dst-port {
          when "../l4-protocol = 'tcp' or ../l4-protocol = 'udp'";
          type port-number-or-any;
          default "any";
          description
            "Single destination port match, or any";
        }

        leaf log {
          type boolean;
          default "false";
          description
            "Enable logging for matched packets";
        }
      }
    }

    /*
     * =================================================================================
     * Operational state
     * =================================================================================
     */
    container state {
      config false;
      description
        "Operational state reported by the CPE agent";

      list wan-link-state {
        key "name";
        description
          "Live state of WAN links";

        leaf name {
          type leafref {
            path "/scpe:sdwan/scpe:interfaces/scpe:underlay/scpe:wan-link/scpe:name";
          }
          description
            "WAN link identifier";
        }

        leaf oper-status {
          type enumeration {
            enum up;
            enum down;
            enum degraded;
          }
          description
            "Current link operational status";
        }

        leaf ipv4-address {
          type inet:ipv4-address;
          description
            "Current IPv4 address on the WAN link";
        }

        leaf gateway-reachable {
          type boolean;
          description
            "Whether the configured or learned gateway is reachable";
        }

        leaf latency-ms {
          type uint32;
          units "ms";
          description
            "Measured latency";
        }

        leaf jitter-ms {
          type uint32;
          units "ms";
          description
            "Measured jitter";
        }

        leaf loss-percent {
          type percentage;
          description
            "Measured packet loss percentage";
        }

        leaf available-bandwidth-kbps {
          type uint32;
          units "kbps";
          description
            "Estimated available bandwidth";
        }
      }

      list tunnel-state {
        key "name";
        description
          "Live state and quality metrics per tunnel";

        leaf name {
          type leafref {
            path "/scpe:sdwan/scpe:overlay/scpe:tunnel/scpe:name";
          }
          description
            "Tunnel name";
        }

        leaf oper-status {
          type enumeration {
            enum up;
            enum down;
            enum degraded;
          }
          description
            "Tunnel health status";
        }

        leaf active-wan-link {
          type leafref {
            path "/scpe:sdwan/scpe:interfaces/scpe:underlay/scpe:wan-link/scpe:name";
          }
          description
            "WAN link currently carrying the tunnel";
        }

        leaf latency-ms {
          type uint32;
          units "ms";
          description
            "Measured latency";
        }

        leaf jitter-ms {
          type uint32;
          units "ms";
          description
            "Measured jitter";
        }

        leaf loss-percent {
          type percentage;
          description
            "Measured packet loss percentage";
        }

        leaf available-bandwidth-kbps {
          type uint32;
          units "kbps";
          description
            "Estimated available bandwidth";
        }

        leaf-list active-class {
          type leafref {
            path "/scpe:sdwan/scpe:traffic/scpe:class/scpe:name";
          }
          description
            "Traffic classes currently steered over this tunnel";
        }
      }
    }
  }
}
